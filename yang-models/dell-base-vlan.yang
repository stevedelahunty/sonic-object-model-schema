module dell-base-vlan {

    namespace "http://www.dell.com/esg/networking/os10/dell-base-vlan";
    prefix "base-vlan";

    import ietf-yang-types {
        prefix yang;
    }

    import dell-base-common {
        prefix "base-cmn";
    }

    organization
        "Dell Inc";

    contact
        "www.dell.com/support/softwarecontacts";

    description
        "This module contains a collection of YANG definitions for managing
        configuration and operational data for Dell VLAN functionality";

    revision 2015-03-01 {
        description "Initial version";
    }

    list entry {
        key "ifindex";
        description "This grouping defines vlan interface object";

        leaf id {
            type base-cmn:vlan-id;
            description "the vlan id associated with interface";
        }

        leaf ifindex {
            type base-cmn:logical-ifindex;
            description "index received from to/kernel for interface";
        }

        leaf name {
            type string;
            description "Name associated with the interface";
        }

        leaf mac-address {
            type base-cmn:mac-address;
            description "Vlan interface MAC Address";
        }

        leaf ip-address {
            type base-cmn:ipv4-address;
            description "IP address associated with the vlan";
        }

        leaf num-ports-untagged {
            type uint32;
            description "number of members in the vlan interface";
        }

        leaf-list untagged-ports {
            type base-cmn:logical-ifindex;
        }

        leaf num-ports-tagged {
            type uint32;
            description "number of members in the vlan interface";
        }

        leaf-list tagged-ports {
            type base-cmn:logical-ifindex;
        }

        leaf enable-statistics {
            type boolean;
            description "Enable/Disable statistics";
        }

        leaf learning-mode {
            type boolean;
            description "Enable/Disable learning per VLAN";
        }

        leaf oper-status {
            type base-cmn:oper-status-type;
            description "Status of the vlan entry";
        }

        leaf admin-status {
            type base-cmn:admin-status-type;
            description "Status of the vlan entry";
        }
    }
}
