module dell-yang-types {
  namespace "http://www.dell.com/ns/amazon-river/dell-yang-types";
  prefix common;

  import ietf-inet-types {
    prefix inet;
  }

  revision 2015-06-04 {
    description
      "Add scp,http,https to typedef protocol-name.";
  }
  revision 2015-03-10 {
    description
      "Initial revision.";
  }

  /*
   * typedefs
   */

  typedef percent {
    description
      "percentage type";
    type uint8 {
      range "0 .. 100";
    }
    units "percent";
  }

  typedef xfloat {
    type decimal64 {
      fraction-digits 3;
    }
    description
      "The decimal or float value type";
  }

  typedef log-intf-types {
    type enumeration {
      enum "logical" {
        value 1;
      }
      enum "cpu" {
        value 2;
      }
      enum "lag" {
        value 3;
      }
      enum "null" {
        value 4;
      }
      enum "loopback" {
        value 5;
      }
      enum "port-channel" {
        value 6;
      }
      enum "vlan" {
        value 7;
      }
      enum "l2-tunnel" {
        value 8;
      }
    }
    description
      "Defines the type of logical interfaces";
  }

  typedef phy-intf-types {
    type enumeration {
      enum "tengigabitethernet" {
        value 1;
      }
      enum "fortyGigaBitEtnernet" {
        value 2;
      }
      enum "gigaBitEthernet" {
        value 3;
      }
    }
    description
      "Defines the type of physical interfaces";
  }

  typedef interface-types {
    type union {
      type phy-intf-types;
      type log-intf-types;
    }
  }

  typedef policy-name {
    type string {
      length "1..140";
      pattern "(([^,=|&\"])|([\\w]))+";
    }
    description
      "Name of the access group or list";
  }

  typedef ipv4-mask-or-prefix {
    type union {
      type inet:ipv4-address;
      type inet:ipv4-prefix;
    }
  }

  typedef ipv6-mask-or-prefix {
    type union {
      type inet:ipv6-address;
      type inet:ipv6-prefix;
    }
  }

  typedef ip-mask-or-prefix {
    type union {
      type ipv4-mask-or-prefix;
      type ipv6-mask-or-prefix;
    }
  }

  typedef as-number-dot {
    type string {
      pattern "((([0-9][0-9]{0,3})|([1-5][0-9]{4})|(6[0-4][0-9]{3})|(65[0-4][0-9]{2})|(655[0-2][0-9])|(6553[0-5]))\\.(([0-9][0-9]{0,3})|([1-5][0-9]{4})|(6[0-4][0-9]{3})|(65[0-4][0-9]{2})|(655[0-2][0-9])|(6553[0-5])))|([1-9][0-9]{0,8})|([1-3][0-9]{9})|(4[0-1][0-9]{8})|(42[0-8][0-9]{7})|(429[0-3][0-9]{6})|(4294[0-8][0-9]{5})|(42949[0-5][0-9]{4})|(429496[0-6][0-9]{3})|(4294967[0-1][0-9]{2})|(42949672[0-8][0-9])|(429496729[0-5])";
    }
    description
      "The as-number type in dot format represents autonomous system numbers
       which identify an Autonomous System.";
  }

  typedef interface-name {
    type string {
      length "0..255";
    }
    description
      "Name of the interface as in ifName";
  }

  typedef admin-status {
    type enumeration {
      enum "admin-up" {
        value 1;
      }
      enum "admin-down" {
        value 2;
      }
    }
    description
      "The desired state of the interface.";
  }

  typedef oper-status {
    type enumeration {
      enum "unknown" {
        value 1;
      }
      enum "up" {
        value 2;
      }
      enum "down" {
        value 3;
      }
      enum "testing" {
        value 4;
      }
      enum "not-present" {
        value 5;
      }
      enum "disabled" {
        value 6;
      }
      enum "diag" {
        value 7;
      }
      enum "linkup" {
        value 8;
      }
    }
    description
      "The current operational state of the interface.";
  }

  typedef vrf-name {
    type string {
      length "0..31";
    }
    description
      "The name of the vrf(virtual routing and forwarding).";
  }

  typedef ethertype {
    type union {
      type string {
        length "3..4";
        pattern "[6-9a-fA-F][0-9a-fA-F][0-9a-fA-f]";
      }
      type string {
        length "3..4";
        pattern "[1-9a-fA-F][0-9a-fA-F][0-9a-fA-F][0-9a-fA-F]";
      }
    }
    description
      "<600-FFFF>;;Ethertype hex value.";
  }

  typedef vlan-range {
    type string {
      length "0..255";
      pattern "([0-9]+|[0-9]+-[0-9]+)(,([0-9]+|[0-9]+-[0-9]+))*";
    }
    description
      "One vlan (1..4094) or a range separated by dash: 1-1 to 4094-4094";
  }

  typedef vlan-range-separated-by-comma {
    type string {
      length "0..255";
      pattern "([0-9]+)|(([0-9]+)(,([0-9]+))*)";
    }
    description
      "One vlan (1..4094) or a range separated by comma:1,2,3";
  }

  typedef vlan-name {
    type string {
      length "0..31";
      pattern "([a-zA-Z])+([.]|[\\S])*";
    }
    description
      "The name of VLAN.";
  }

  typedef vlan-id {
    type uint16 {
      range "1..4094";
    }
    description
      "The number or id of VLAN.";
  }

  typedef direction-enumeration {
    type enumeration {
      enum "in" {
        value 1;
      }
      enum "out" {
        value 2;
      }
      enum "both" {
        value 3;
      }
    }
    description
      "used to represent in or out direction.";
  }

  typedef vrf-id {
    type uint32 {
      range "1..512";
    }
    description
      "vrf id value.";
  }

  typedef protocol-name {
    type enumeration {
      enum "bgp" {
        value 1;
      }
      enum "dhcp" {
        value 2;
      }
      enum "dhcp-relay" {
        value 3;
      }
      enum "ftp" {
        value 4;
      }
      enum "icmp" {
        value 5;
      }
      enum "igmp" {
        value 6;
      }
      enum "msdp" {
        value 7;
      }
      enum "ntp" {
        value 8;
      }
      enum "ospf" {
        value 9;
      }
      enum "pim" {
        value 10;
      }
      enum "rip" {
        value 11;
      }
      enum "ssh" {
        value 12;
      }
      enum "telnet" {
        value 13;
      }
      enum "vrrp" {
        value 14;
      }
      enum "ip" {
        value 15;
      }
      enum "tcp" {
        value 16;
      }
      enum "udp" {
        value 17;
      }
      enum "ipv6" {
        value 18;
      }
      enum "arp" {
        value 19;
      }
      enum "bridging" {
        value 20;
      }
      enum "cdp" {
        value 21;
      }
      enum "is-is" {
        value 22;
      }
      enum "scp" {
        value 23;
      }
      enum "http" {
        value 24;
      }
      enum "https" {
        value 25;
      }
      enum "frrp" {
        value 26;
      }
      enum "gvrp" {
        value 27;
      }
      enum "lacp" {
        value 28;
      }
      enum "lldp" {
        value 29;
      }
      enum "stp" {
        value 30;
      }
    }
    description
      "List of protocols names.";
  }
}
